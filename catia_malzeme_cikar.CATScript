' ==========================================================================
'  Pi3D - CATIA V5 malzeme cikarma makrosu
'
'  Acik olan .CATProduct'in agacini gezer, her parcanin malzemesini ve
'  KAYNAGINI (Ozellikler > Urun > Source: Made / Bought) okur, urun
'  dosyasinin yanina "malzeme.csv" yazar:
'
'      kod;malzeme;ad;kaynak
'      01.050.000.01;Steel;U-Blech-Mechanismus;Made
'      ISO 4762 M6x20;Steel;Civata;Bought
'
'  kaynak = Bought olan parca Pi3D'de SATIN ALINAN (standart) sayilir,
'  resmi cizilmez; Made olan uretim parcasidir. Alt montaj Bought ise
'  altindaki butun parcalar Bought sayilir (satin alinan grup).
'
'  Bu dosyayi Pi3D'de: Yardim > Malzemeyi CAD'den al > 4. adim ile verin.
'
'  Calistirmak: Tools > Macro > Macros... > Select an external file >
'               bu dosyayi secip Run.
'
'  NOT: Malzeme okuma arayuzu CATIA surumune gore degisebilir; makro uc
'  ayri yolu sirayla dener. Hicbiri tutmazsa menuden
'  Analyze > Bill of Material yolunu kullanin - o kesin calisir,
'  ayrintisi CATIA_MALZEME.md dosyasinda.
' ==========================================================================

Option Explicit

Sub CATMain()

    Dim oDoc
    Set oDoc = CATIA.ActiveDocument
    If InStr(1, TypeName(oDoc), "Product", 1) = 0 Then
        MsgBox "Once bir .CATProduct acin.", vbExclamation, "Pi3D"
        Exit Sub
    End If

    Dim yol
    yol = Left(oDoc.FullName, InStrRev(oDoc.FullName, "\")) & "malzeme.csv"

    Dim fso, f
    Set fso = CreateObject("Scripting.FileSystemObject")
    Set f = fso.CreateTextFile(yol, True)
    f.WriteLine "kod;malzeme;ad;kaynak"

    Dim sayac, bulunan
    sayac = 0 : bulunan = 0
    Gez oDoc.Product, f, sayac, bulunan, ""

    f.Close
    MsgBox "Yazildi:" & vbCrLf & yol & vbCrLf & vbCrLf & _
           sayac & " parca gezildi, " & bulunan & " tanesinde malzeme bulundu." & _
           vbCrLf & vbCrLf & _
           "Bu dosyayi Pi3D'de: Yardim > Malzemeyi CAD'den al > 4. adim", _
           vbInformation, "Pi3D"

End Sub


' Montaj agacini yinelemeli gezer. ustKaynak: ust montaj Bought ise
' altindakiler de Bought yazilir.
Sub Gez(oUrun, f, sayac, bulunan, ustKaynak)

    Dim i, oAlt, kay
    kay = KaynakAdi(oUrun)
    If ustKaynak = "Bought" Then kay = "Bought"
    If oUrun.Products.Count > 0 Then
        For i = 1 To oUrun.Products.Count
            Set oAlt = oUrun.Products.Item(i)
            Gez oAlt, f, sayac, bulunan, kay
        Next
        Exit Sub
    End If

    ' Yaprak dugum: gercek parca
    sayac = sayac + 1

    Dim kod, ad, mal
    kod = Temizle(oUrun.PartNumber)
    ad = Temizle(oUrun.Name)
    mal = MalzemeAdi(oUrun)
    If mal <> "" Then bulunan = bulunan + 1

    f.WriteLine kod & ";" & mal & ";" & ad & ";" & kay

End Sub


' Urunun Source alani: 1 = Made (uretilen), 2 = Bought (satin alinan),
' 0 = Unknown. Alan dogrudan urunde ya da referans urunde olabilir.
Function KaynakAdi(oUrun)

    Dim s
    s = 0
    On Error Resume Next
    s = oUrun.Source
    If Err.Number <> 0 Or s = 0 Then
        Err.Clear
        s = oUrun.ReferenceProduct.Source
    End If
    On Error GoTo 0
    If s = 1 Then
        KaynakAdi = "Made"
    ElseIf s = 2 Then
        KaynakAdi = "Bought"
    Else
        KaynakAdi = ""
    End If

End Function


' Malzeme adini uc ayri yoldan okumaya calisir.
Function MalzemeAdi(oUrun)

    Dim ad
    ad = ""

    ' 1) Urun dugumunun kendi malzemesi
    On Error Resume Next
    ad = oUrun.Material.Name
    On Error GoTo 0
    If ad <> "" Then MalzemeAdi = Temizle(ad) : Exit Function

    ' 2) Parcanin malzemesi (CATMatManagerVBExt)
    Dim oPartDoc, oYonetici, oMat
    On Error Resume Next
    Set oPartDoc = oUrun.ReferenceProduct.Parent
    Set oYonetici = oPartDoc.Part.GetItem("CATMatManagerVBExt")
    Set oMat = oYonetici.GetMaterialOnPart(oPartDoc.Part)
    ad = oMat.Name
    On Error GoTo 0
    If ad <> "" Then MalzemeAdi = Temizle(ad) : Exit Function

    ' 3) Ana govdenin malzemesi
    On Error Resume Next
    Set oMat = oYonetici.GetMaterialOnBody(oPartDoc.Part.MainBody)
    ad = oMat.Name
    On Error GoTo 0
    If ad <> "" Then MalzemeAdi = Temizle(ad) : Exit Function

    MalzemeAdi = ""

End Function


' Noktali virgulu ve satir sonunu temizler, CSV bozulmasin.
Function Temizle(metin)
    Dim t
    t = metin
    t = Replace(t, ";", ",")
    t = Replace(t, vbCr, " ")
    t = Replace(t, vbLf, " ")
    Temizle = Trim(t)
End Function
